-- ASN1START
-- **************************************************************
--
-- Constant definitions
--
-- **************************************************************

NGAP-Constants { 
itu-t (0) identified-organization (4) etsi (0) mobileDomain (0) 
ngran-Access (22) modules (3) ngap (1) version1 (1) ngap-Constants (4) } 

DEFINITIONS AUTOMATIC TAGS ::= 

BEGIN

-- **************************************************************
--
-- IE parameter types from other modules.
--
-- **************************************************************

IMPORTS

	Ngap-ProcedureCode,
	Ngap-ProtocolIE-ID
FROM NGAP-CommonDataTypes;


-- **************************************************************
--
-- Elementary Procedures
--
-- **************************************************************

id-AMFConfigurationUpdate					Ngap-ProcedureCode ::= 0
id-AMFStatusIndication						Ngap-ProcedureCode ::= 1
id-CellTrafficTrace							Ngap-ProcedureCode ::= 2
id-DeactivateTrace							Ngap-ProcedureCode ::= 3
id-DownlinkNASTransport						Ngap-ProcedureCode ::= 4
id-DownlinkNonUEAssociatedNRPPaTransport	Ngap-ProcedureCode ::= 5
id-DownlinkRANConfigurationTransfer			Ngap-ProcedureCode ::= 6
id-DownlinkRANStatusTransfer				Ngap-ProcedureCode ::= 7
id-DownlinkUEAssociatedNRPPaTransport		Ngap-ProcedureCode ::= 8
id-ErrorIndication							Ngap-ProcedureCode ::= 9
id-HandoverCancel							Ngap-ProcedureCode ::= 10
id-HandoverNotification						Ngap-ProcedureCode ::= 11
id-HandoverPreparation						Ngap-ProcedureCode ::= 12
id-HandoverResourceAllocation				Ngap-ProcedureCode ::= 13
id-InitialContextSetup						Ngap-ProcedureCode ::= 14
id-InitialUEMessage							Ngap-ProcedureCode ::= 15
id-LocationReportingControl					Ngap-ProcedureCode ::= 16
id-LocationReportingFailureIndication		Ngap-ProcedureCode ::= 17
id-LocationReport							Ngap-ProcedureCode ::= 18
id-NASNonDeliveryIndication					Ngap-ProcedureCode ::= 19
id-NGReset									Ngap-ProcedureCode ::= 20
id-NGSetup									Ngap-ProcedureCode ::= 21
id-OverloadStart							Ngap-ProcedureCode ::= 22
id-OverloadStop								Ngap-ProcedureCode ::= 23
id-Paging									Ngap-ProcedureCode ::= 24
id-PathSwitchRequest						Ngap-ProcedureCode ::= 25
id-PDUSessionResourceModify					Ngap-ProcedureCode ::= 26
id-PDUSessionResourceModifyIndication		Ngap-ProcedureCode ::= 27
id-PDUSessionResourceRelease				Ngap-ProcedureCode ::= 28
id-PDUSessionResourceSetup					Ngap-ProcedureCode ::= 29
id-PDUSessionResourceNotify					Ngap-ProcedureCode ::= 30
id-PrivateMessage							Ngap-ProcedureCode ::= 31
id-PWSCancel								Ngap-ProcedureCode ::= 32
id-PWSFailureIndication						Ngap-ProcedureCode ::= 33
id-PWSRestartIndication						Ngap-ProcedureCode ::= 34
id-RANConfigurationUpdate					Ngap-ProcedureCode ::= 35
id-RerouteNASRequest						Ngap-ProcedureCode ::= 36
id-RRCInactiveTransitionReport				Ngap-ProcedureCode ::= 37
id-TraceFailureIndication					Ngap-ProcedureCode ::= 38
id-TraceStart								Ngap-ProcedureCode ::= 39
id-UEContextModification					Ngap-ProcedureCode ::= 40
id-UEContextRelease							Ngap-ProcedureCode ::= 41
id-UEContextReleaseRequest					Ngap-ProcedureCode ::= 42
id-UERadioCapabilityCheck					Ngap-ProcedureCode ::= 43
id-UERadioCapabilityInfoIndication			Ngap-ProcedureCode ::= 44
id-UETNLABindingRelease						Ngap-ProcedureCode ::= 45
id-UplinkNASTransport						Ngap-ProcedureCode ::= 46
id-UplinkNonUEAssociatedNRPPaTransport		Ngap-ProcedureCode ::= 47
id-UplinkRANConfigurationTransfer			Ngap-ProcedureCode ::= 48
id-UplinkRANStatusTransfer					Ngap-ProcedureCode ::= 49
id-UplinkUEAssociatedNRPPaTransport			Ngap-ProcedureCode ::= 50
id-WriteReplaceWarning						Ngap-ProcedureCode ::= 51

-- **************************************************************
--
-- Extension constants
--
-- **************************************************************

ngap-maxPrivateIEs							INTEGER ::= 65535
ngap-maxProtocolExtensions					INTEGER ::= 65535
ngap-maxProtocolIEs							INTEGER ::= 65535

-- **************************************************************
--
-- Lists
--
-- **************************************************************

	ngap-maxnoofAllowedAreas					INTEGER ::= 16
	ngap-maxnoofAllowedS-NSSAIs				INTEGER ::= 8
	ngap-maxnoofBPLMNs						INTEGER ::= 12
	ngap-maxnoofCellIDforWarning				INTEGER ::= 65535
	ngap-maxnoofCellinAoI					INTEGER ::= 256
	ngap-maxnoofCellinEAI					INTEGER ::= 65535
	ngap-maxnoofCellinTAI					INTEGER ::= 65535
	ngap-maxnoofCellsingNB					INTEGER ::= 16384
	ngap-maxnoofCellsinngeNB					INTEGER ::= 256
	ngap-maxnoofCellsinUEHistoryInfo			INTEGER ::= 16
	ngap-maxnoofCellsUEMovingTrajectory		INTEGER ::= 16
	ngap-maxnoofDRBs							INTEGER ::= 32
	ngap-maxnoofEmergencyAreaID				INTEGER ::= 65535
	ngap-maxnoofEAIforRestart				INTEGER ::= 256
	ngap-maxnoofEPLMNs						INTEGER ::= 15
	ngap-maxnoofEPLMNsPlusOne				INTEGER ::= 16
	ngap-maxnoofE-RABs						INTEGER ::= 256
	ngap-maxnoofErrors						INTEGER ::= 256
	ngap-maxnoofForbTACs						INTEGER ::= 4096
	ngap-maxnoofMultiConnectivities			INTEGER ::= 4
	ngap-maxnoofNGConnectionsToReset			INTEGER ::= 65536
	ngap-maxnoofPDUSessions					INTEGER ::= 256
	ngap-maxnoofPLMNs						INTEGER ::= 12
	ngap-maxnoofQosFlows						INTEGER ::= 64
	ngap-maxnoofRANNodeinAoI					INTEGER ::= 64
	ngap-maxnoofRecommendedCells				INTEGER ::= 16
	ngap-maxnoofRecommendedRANNodes			INTEGER ::= 16
	ngap-maxnoofAoI							INTEGER ::= 64
	ngap-maxnoofServedGUAMIs					INTEGER ::= 256
	ngap-maxnoofSliceItems					INTEGER ::= 1024
	ngap-maxnoofTACs							INTEGER ::= 256
	ngap-maxnoofTAIforInactive				INTEGER ::= 16
	ngap-maxnoofTAIforPaging					INTEGER ::= 16
	ngap-maxnoofTAIforRestart				INTEGER ::= 2048
	ngap-maxnoofTAIforWarning				INTEGER ::= 65535
	ngap-maxnoofTAIinAoI						INTEGER ::= 16
	ngap-maxnoofTNLAssociations				INTEGER ::= 32
	ngap-maxnoofXnExtTLAs					INTEGER ::= 2
	ngap-maxnoofXnGTP-TLAs					INTEGER ::= 16
	ngap-maxnoofXnTLAs						INTEGER ::= 16

-- **************************************************************
--
-- IEs
--
-- **************************************************************

	id-AllowedNSSAI											Ngap-ProtocolIE-ID ::= 0
	id-AMFName												Ngap-ProtocolIE-ID ::= 1
	id-AMFOverloadResponse									Ngap-ProtocolIE-ID ::= 2
	id-AMFSetID												Ngap-ProtocolIE-ID ::= 3
	id-AMF-TNLAssociationFailedToSetupList					Ngap-ProtocolIE-ID ::= 4
	id-AMF-TNLAssociationSetupList							Ngap-ProtocolIE-ID ::= 5
	id-AMF-TNLAssociationToAddList							Ngap-ProtocolIE-ID ::= 6
	id-AMF-TNLAssociationToRemoveList						Ngap-ProtocolIE-ID ::= 7
	id-AMF-TNLAssociationToUpdateList						Ngap-ProtocolIE-ID ::= 8
	id-AMFTrafficLoadReductionIndication					Ngap-ProtocolIE-ID ::= 9
	id-AMF-UE-NGAP-ID										Ngap-ProtocolIE-ID ::= 10
	id-AssistanceDataForPaging								Ngap-ProtocolIE-ID ::= 11
	id-BroadcastCancelledAreaList							Ngap-ProtocolIE-ID ::= 12
	id-BroadcastCompletedAreaList							Ngap-ProtocolIE-ID ::= 13
	id-CancelAllWarningMessages								Ngap-ProtocolIE-ID ::= 14
	id-Cause												Ngap-ProtocolIE-ID ::= 15
	id-CellIDListForRestart									Ngap-ProtocolIE-ID ::= 16
	id-ConcurrentWarningMessageInd							Ngap-ProtocolIE-ID ::= 17
	id-CoreNetworkAssistanceInformation						Ngap-ProtocolIE-ID ::= 18
	id-CriticalityDiagnostics								Ngap-ProtocolIE-ID ::= 19
	id-DataCodingScheme										Ngap-ProtocolIE-ID ::= 20
	id-DefaultPagingDRX										Ngap-ProtocolIE-ID ::= 21
	id-DirectForwardingPathAvailability						Ngap-ProtocolIE-ID ::= 22
	id-EmergencyAreaIDListForRestart						Ngap-ProtocolIE-ID ::= 23
	id-EmergencyFallbackIndicator							Ngap-ProtocolIE-ID ::= 24
	id-EUTRA-CGI											Ngap-ProtocolIE-ID ::= 25
	id-FiveG-S-TMSI											Ngap-ProtocolIE-ID ::= 26
	id-GlobalRANNodeID										Ngap-ProtocolIE-ID ::= 27
	id-GUAMI												Ngap-ProtocolIE-ID ::= 28
	id-HandoverType											Ngap-ProtocolIE-ID ::= 29
	id-IMSVoiceSupportIndicator								Ngap-ProtocolIE-ID ::= 30
	id-IndexToRFSP											Ngap-ProtocolIE-ID ::= 31
	id-InfoOnRecommendedCellsAndRANNodesForPaging			Ngap-ProtocolIE-ID ::= 32
	id-LocationReportingRequestType							Ngap-ProtocolIE-ID ::= 33
	id-MaskedIMEISV											Ngap-ProtocolIE-ID ::= 34
	id-MessageIdentifier									Ngap-ProtocolIE-ID ::= 35
	id-MobilityRestrictionList								Ngap-ProtocolIE-ID ::= 36
	id-NASC													Ngap-ProtocolIE-ID ::= 37
	id-NAS-PDU												Ngap-ProtocolIE-ID ::= 38
	id-NASSecurityParametersFromNGRAN						Ngap-ProtocolIE-ID ::= 39
	id-NewAMF-UE-NGAP-ID									Ngap-ProtocolIE-ID ::= 40
	id-NewSecurityContextInd								Ngap-ProtocolIE-ID ::= 41
	id-NGAP-Message											Ngap-ProtocolIE-ID ::= 42
	id-NGRAN-CGI											Ngap-ProtocolIE-ID ::= 43
	id-NGRANTraceID											Ngap-ProtocolIE-ID ::= 44
	id-NR-CGI												Ngap-ProtocolIE-ID ::= 45
	id-NRPPa-PDU											Ngap-ProtocolIE-ID ::= 46
	id-NumberOfBroadcastsRequested							Ngap-ProtocolIE-ID ::= 47
	id-OldAMF												Ngap-ProtocolIE-ID ::= 48
	id-OverloadStartNSSAIList								Ngap-ProtocolIE-ID ::= 49
	id-PagingDRX											Ngap-ProtocolIE-ID ::= 50
	id-PagingOrigin											Ngap-ProtocolIE-ID ::= 51
	id-PagingPriority										Ngap-ProtocolIE-ID ::= 52
	id-PDUSessionResourceAdmittedList						Ngap-ProtocolIE-ID ::= 53
	id-PDUSessionResourceFailedToModifyListModRes			Ngap-ProtocolIE-ID ::= 54
	id-PDUSessionResourceFailedToSetupListCxtRes			Ngap-ProtocolIE-ID ::= 55
	id-PDUSessionResourceFailedToSetupListHOAck				Ngap-ProtocolIE-ID ::= 56
	id-PDUSessionResourceFailedToSetupListPSReq				Ngap-ProtocolIE-ID ::= 57
	id-PDUSessionResourceFailedToSetupListSURes				Ngap-ProtocolIE-ID ::= 58
	id-PDUSessionResourceHandoverList						Ngap-ProtocolIE-ID ::= 59
	id-PDUSessionResourceListCxtRelCpl						Ngap-ProtocolIE-ID ::= 60
	id-PDUSessionResourceListHORqd							Ngap-ProtocolIE-ID ::= 61
	id-PDUSessionResourceModifyListModCfm					Ngap-ProtocolIE-ID ::= 62
	id-PDUSessionResourceModifyListModInd					Ngap-ProtocolIE-ID ::= 63
	id-PDUSessionResourceModifyListModReq					Ngap-ProtocolIE-ID ::= 64
	id-PDUSessionResourceModifyListModRes					Ngap-ProtocolIE-ID ::= 65
	id-PDUSessionResourceNotifyList							Ngap-ProtocolIE-ID ::= 66
	id-PDUSessionResourceReleasedListNot					Ngap-ProtocolIE-ID ::= 67
	id-PDUSessionResourceReleasedListPSAck					Ngap-ProtocolIE-ID ::= 68
	id-PDUSessionResourceReleasedListPSFail					Ngap-ProtocolIE-ID ::= 69
	id-PDUSessionResourceReleasedListRelRes					Ngap-ProtocolIE-ID ::= 70
	id-PDUSessionResourceSetupListCxtReq					Ngap-ProtocolIE-ID ::= 71
	id-PDUSessionResourceSetupListCxtRes					Ngap-ProtocolIE-ID ::= 72
	id-PDUSessionResourceSetupListHOReq						Ngap-ProtocolIE-ID ::= 73
	id-PDUSessionResourceSetupListSUReq						Ngap-ProtocolIE-ID ::= 74
	id-PDUSessionResourceSetupListSURes						Ngap-ProtocolIE-ID ::= 75
	id-PDUSessionResourceToBeSwitchedDLList					Ngap-ProtocolIE-ID ::= 76
	id-PDUSessionResourceSwitchedList						Ngap-ProtocolIE-ID ::= 77
	id-PDUSessionResourceToReleaseListHOCmd					Ngap-ProtocolIE-ID ::= 78
	id-PDUSessionResourceToReleaseListRelCmd				Ngap-ProtocolIE-ID ::= 79
	id-PLMNSupportList										Ngap-ProtocolIE-ID ::= 80
	id-PWSFailedCellIDList									Ngap-ProtocolIE-ID ::= 81
	id-RANNodeName											Ngap-ProtocolIE-ID ::= 82
	id-RANPagingPriority									Ngap-ProtocolIE-ID ::= 83
	id-RANStatusTransfer-TransparentContainer				Ngap-ProtocolIE-ID ::= 84
	id-RAN-UE-NGAP-ID										Ngap-ProtocolIE-ID ::= 85
	id-RelativeAMFCapacity									Ngap-ProtocolIE-ID ::= 86
	id-RepetitionPeriod										Ngap-ProtocolIE-ID ::= 87
	id-ResetType											Ngap-ProtocolIE-ID ::= 88
	id-RoutingID											Ngap-ProtocolIE-ID ::= 89
	id-RRCEstablishmentCause								Ngap-ProtocolIE-ID ::= 90
	id-RRCInactiveTransitionReportRequest					Ngap-ProtocolIE-ID ::= 91
	id-RRCState												Ngap-ProtocolIE-ID ::= 92
	id-SecurityContext										Ngap-ProtocolIE-ID ::= 93
	id-SecurityKey											Ngap-ProtocolIE-ID ::= 94
	id-SerialNumber											Ngap-ProtocolIE-ID ::= 95
	id-ServedGUAMIList										Ngap-ProtocolIE-ID ::= 96
	id-SliceSupportList										Ngap-ProtocolIE-ID ::= 97
	id-SONConfigurationTransferDL							Ngap-ProtocolIE-ID ::= 98
	id-SONConfigurationTransferUL							Ngap-ProtocolIE-ID ::= 99
	id-SourceAMF-UE-NGAP-ID									Ngap-ProtocolIE-ID ::= 100
	id-SourceToTarget-TransparentContainer					Ngap-ProtocolIE-ID ::= 101
	id-SupportedTAList										Ngap-ProtocolIE-ID ::= 102
	id-TAIListForPaging										Ngap-ProtocolIE-ID ::= 103
	id-TAIListForRestart									Ngap-ProtocolIE-ID ::= 104
	id-TargetID												Ngap-ProtocolIE-ID ::= 105
	id-TargetToSource-TransparentContainer					Ngap-ProtocolIE-ID ::= 106
	id-TimeToWait											Ngap-ProtocolIE-ID ::= 107
	id-TraceActivation										Ngap-ProtocolIE-ID ::= 108
	id-TraceCollectionEntityIPAddress						Ngap-ProtocolIE-ID ::= 109
	id-UEAggregateMaximumBitRate							Ngap-ProtocolIE-ID ::= 110
	id-UE-associatedLogicalNG-connectionList				Ngap-ProtocolIE-ID ::= 111
	id-UEContextRequest										Ngap-ProtocolIE-ID ::= 112
	id-UE-NGAP-IDs											Ngap-ProtocolIE-ID ::= 114
	id-UEPagingIdentity										Ngap-ProtocolIE-ID ::= 115
	id-UEPresenceInAreaOfInterestList						Ngap-ProtocolIE-ID ::= 116
	id-UERadioCapability									Ngap-ProtocolIE-ID ::= 117
	id-UERadioCapabilityForPaging							Ngap-ProtocolIE-ID ::= 118
	id-UESecurityCapabilities								Ngap-ProtocolIE-ID ::= 119
	id-UnavailableGUAMIList									Ngap-ProtocolIE-ID ::= 120
	id-UserLocationInformation								Ngap-ProtocolIE-ID ::= 121
	id-WarningAreaList										Ngap-ProtocolIE-ID ::= 122
	id-WarningMessageContents								Ngap-ProtocolIE-ID ::= 123
	id-WarningSecurityInfo									Ngap-ProtocolIE-ID ::= 124
	id-WarningType											Ngap-ProtocolIE-ID ::= 125
	id-AdditionalUL-NGU-UP-TNLInformation					Ngap-ProtocolIE-ID ::= 126
	id-DataForwardingNotPossible							Ngap-ProtocolIE-ID ::= 127
	id-DL-NGU-UP-TNLInformation								Ngap-ProtocolIE-ID ::= 128
	id-NetworkInstance										Ngap-ProtocolIE-ID ::= 129
	id-PDUSessionAggregateMaximumBitRate					Ngap-ProtocolIE-ID ::= 130
	id-PDUSessionResourceFailedToModifyListModCfm			Ngap-ProtocolIE-ID ::= 131
	id-PDUSessionResourceFailedToSetupListCxtFail			Ngap-ProtocolIE-ID ::= 132
	id-PDUSessionResourceListCxtRelReq						Ngap-ProtocolIE-ID ::= 133
	id-PDUSessionType										Ngap-ProtocolIE-ID ::= 134
	id-QosFlowAddOrModifyRequestList						Ngap-ProtocolIE-ID ::= 135
	id-QosFlowSetupRequestList								Ngap-ProtocolIE-ID ::= 136
	id-QosFlowToReleaseList									Ngap-ProtocolIE-ID ::= 137
	id-SecurityIndication									Ngap-ProtocolIE-ID ::= 138
	id-UL-NGU-UP-TNLInformation								Ngap-ProtocolIE-ID ::= 139
	id-UL-NGU-UP-TNLModifyList								Ngap-ProtocolIE-ID ::= 140
	id-WarningAreaCoordinates								Ngap-ProtocolIE-ID ::= 141

END
-- ASN1STOP
